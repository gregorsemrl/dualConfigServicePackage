module dualConfigService {

  namespace "http://www.cisco.com/trainingExamples/dualConfigService";
  prefix cisco-trn-dualConfigService;

  import ietf-inet-types {
    prefix inet;
  }

  import tailf-ncs {
    prefix ncs;
  }

  import tailf-common {
    prefix tailf;
  }

  revision 2020-10-07 { 
    description "Version 2.0.0.0 of the service with additional 
    support for ACLs defined per device (custom per device).
    
    Migration procedure is introduced which applies configuration
    based on the configurationVersion parameter for existing instances
    (template selection), for completely new instances, new templates are used.
    ";
  }

  revision 2020-09-01 { 
    description "Version 1.0.0.0 of the service with ACL support.";
  }

  augment /ncs:services {
    list dualConfigService {
      tailf:info "Service for IP blacklist ACL support";
      key name;

      uses ncs:service-data;
      ncs:servicepoint "dualConfigService-svcpoint";

      // this is a new structure in v2
      leaf configurationVersion {
        tailf:info "Package migration info, logic applies old or new template based on the parameter.";
        type enumeration {
          enum v1 { value 1; }
          enum v2 { value 2;}
        }
        default v1;
      }

      leaf name {
        tailf:info "Service instance name - extended ACL name applied to our devices";
        type string;
      }
      
      list device {
        tailf:info "List of devices where IP access list is applied";
        key name;
        min-elements 1;
        
        
        leaf name {
          tailf:info "Device name";
          type leafref {
            path "/ncs:devices/ncs:device/ncs:name"; 
          }
        }

        // this is a new structure in v2
        list blacklist-custom {
          tailf:info "List of blacklisted IPs custom to this device";
          key "ip-address";

          leaf ip-address {
            tailf:info "IP address";
            type inet:ipv4-address;
            mandatory true;
          }

          leaf description {
            tailf:info "Additional entry description";
            type string;
          }
        }
      }

      list blacklist-common {
        tailf:info "List of blacklisted IPs common to all devices";
        key "ip-address";

        leaf ip-address {
          tailf:info "IP address";
          type inet:ipv4-address;
          mandatory true;
        }

        leaf description {
          tailf:info "Additional entry description";
          type string;
        }
      }

    }
  }
}
